[DOCUMENT]
TITLE: BenchDouble System Requirements Baseline
UID: BD-BASELINE
VERSION: 2026-10-15

[REQUIREMENT]
UID: TR-001
STATUS: Active
TITLE: TR-001 P0
STATEMENT: One structured procedure definition with stable ID, title, controlled revision, author, parameters, instrument requirements, step tree, acceptance criteria, and approval status.

[REQUIREMENT]
UID: TR-002
STATUS: Active
TITLE: TR-002 P0
STATEMENT: The editor and runner operate on the same structured procedure model, not parallel HTML/code representations.

[REQUIREMENT]
UID: TR-003
STATUS: Active
TITLE: TR-003 P0
STATEMENT: Insert before/after, delete, duplicate, move, reorder, indent/outdent and renumber steps without changing stable step IDs.

[REQUIREMENT]
UID: TR-004
STATUS: Active
TITLE: TR-004 P0
STATEMENT: Step types: instruction, instrument configuration, measurement with limits, calculation, wait, condition/branch, loop, operator prompt, inspection, safety hold, attachment, signature, C# action, and subprocedure.

[REQUIREMENT]
UID: TR-005
STATUS: Active
TITLE: TR-005 P1
STATEMENT: Typed step inputs, defaults, enums, UnitsNet quantities, validation and help text.

[REQUIREMENT]
UID: TR-006
STATUS: Active
TITLE: TR-006 P0
STATEMENT: Draft, approved procedure revision, execution snapshot, redline, and deviation are separate versioned records.

[REQUIREMENT]
UID: TR-007
STATUS: Active
TITLE: TR-007 P0
STATEMENT: Executions pin the exact approved revision/hash; redlines cannot silently overwrite it.

[REQUIREMENT]
UID: TR-008
STATUS: Active
TITLE: TR-008 P1
STATEMENT: Step templates, reusable subprocedures, library search, cross-references and dependency validation.

[REQUIREMENT]
UID: TR-009
STATUS: Active
TITLE: TR-009 P1
STATEMENT: Transactional edits, undo/redo, deterministic serialization, position mapping and autosave.

[REQUIREMENT]
UID: TR-010
STATUS: Active
TITLE: TR-010 P1
STATEMENT: Inline review comments, change diffs, history and reviewer workflow.

[REQUIREMENT]
UID: TR-011
STATUS: Active
TITLE: TR-011 P1
STATEMENT: C# custom-action editing with compilation diagnostics and typed instrument APIs, but not as the underlying document format.

[REQUIREMENT]
UID: TR-012
STATUS: Active
TITLE: TR-012 P1
STATEMENT: Editor technology remains replaceable; Monaco may become the step editor or code editor. Do not prematurely constrain the structured document model to Monaco.

[REQUIREMENT]
UID: TR-013
STATUS: Active
TITLE: TR-013 P1
STATEMENT: Preserve the independently specified C#-centric structured editor engine direction: no required ProseMirror/Tiptap dependency; browser JavaScript only for necessary interop.

[REQUIREMENT]
UID: TR-014
STATUS: Active
TITLE: TR-014 P2
STATEMENT: Accessible keyboard navigation, IME, rich text, tables, attachments and eventual multi-user editing with conflict handling.

[REQUIREMENT]
UID: TR-015
STATUS: Active
TITLE: TR-015 P0
STATEMENT: Run identity, pinned revision, operator, backend, parameters, instrument inventory, start/finish times, status and outcome. Acceptance: The in-memory result sink copies field and unit dictionaries into detached read-only snapshots under a nonempty run identity before one enqueue. Samples allow at most 256 finite fields, field names up to 128 display characters, and associated unit text up to 80 characters without controls. Cancellation or validation failure cannot enqueue partial evidence. This in-memory sink does not claim durable storage acceptance.


[REQUIREMENT]
UID: TR-016
STATUS: Active
TITLE: TR-016 P0
STATEMENT: Auditable states: Created, Validating, Reserving, Startup, Running, Cleanup, Completed, Failed, Cancelled, RecoveryRequired.

[REQUIREMENT]
UID: TR-017
STATUS: Active
TITLE: TR-017 P0
STATEMENT: Explicit startup/execute/shutdown phases; cleanup executes after success, exception or cancellation. Acceptance: Runner admission captures a bounded display name once. Cancellation observed after startup or execution cannot publish success; shutdown still runs with an independent token. Null lifecycle tasks have explicit failures. Throwing cancellation callbacks during cleanup timeout cannot escape recovery-required classification or permit a new run; original execution and cleanup errors remain available.


[REQUIREMENT]
UID: TR-018
STATUS: Active
TITLE: TR-018 P0
STATEMENT: Cleanup has a bounded policy and device-specific abort/disable confirmation; failure reports OutcomeUnknown/RecoveryRequired. Acceptance: Runner shutdown policies reject durations outside the positive platform timer interval before procedure admission. Timeout cleanup retains recovery fencing even if cancellation callbacks throw; no safe physical state or completed driver abort is inferred.


[REQUIREMENT]
UID: TR-019
STATUS: Active
TITLE: TR-019 P0
STATEMENT: Validate procedure inputs, driver capabilities, permissions and resource availability before physical actuation.

[REQUIREMENT]
UID: TR-020
STATUS: Active
TITLE: TR-020 P0
STATEMENT: Async Task/ValueTask, CancellationToken, deadlines, Task.WhenAll/WhenAny and IAsyncEnumerable for streaming.

[REQUIREMENT]
UID: TR-021
STATUS: Active
TITLE: TR-021 P0
STATEMENT: Serialize per-instrument commands and full query/response transactions; independent devices may operate concurrently.

[REQUIREMENT]
UID: TR-022
STATUS: Active
TITLE: TR-022 P0
STATEMENT: Cancelling an awaited task does not imply physical acquisition abort or safe-state confirmation.

[REQUIREMENT]
UID: TR-023
STATUS: Active
TITLE: TR-023 P1
STATEMENT: Queue/schedule runs with fairness, progress, priority, operator holds and resource-aware admission.

[REQUIREMENT]
UID: TR-024
STATUS: Active
TITLE: TR-024 P1
STATEMENT: Pause, resume, skip, retry, abort and approved checkpoint restart with clear audit and idempotency semantics.

[REQUIREMENT]
UID: TR-025
STATUS: Active
TITLE: TR-025 P1
STATEMENT: Reserve all required instruments before coordinated execution; deadlock-free host-local atomic grants and failure-aware multi-host acquisition.

[REQUIREMENT]
UID: TR-026
STATUS: Active
TITLE: TR-026 P1
STATEMENT: Support dependencies and partial-order barriers between concurrent operations; don't impose arbitrary global total order.

[REQUIREMENT]
UID: TR-027
STATUS: Active
TITLE: TR-027 P1
STATEMENT: Live per-step state, progress, measurements, logs and errors, with reconciliation after browser/network disconnect.

[REQUIREMENT]
UID: TR-028
STATUS: Active
TITLE: TR-028 P2
STATEMENT: Parameter sweeps, nested procedures, streaming acquisitions and reusable calculations.

[REQUIREMENT]
UID: TR-029
STATUS: Active
TITLE: TR-029 P0
STATEMENT: Same procedure code runs with physical, simulated and strict-mock backends.

[REQUIREMENT]
UID: TR-030
STATUS: Active
TITLE: TR-030 P0
STATEMENT: Instrument host is a separate, platform-neutral service: any supported computer with the necessary .NET runtime and instrument drivers.

[REQUIREMENT]
UID: TR-031
STATUS: Active
TITLE: TR-031 P0
STATEMENT: Host is authoritative for resource identity, ownership, device operations and reservation policy; clients cannot bypass it.

[REQUIREMENT]
UID: TR-032
STATUS: Active
TITLE: TR-032 P0
STATEMENT: Exclusive control default; leases identity-bound with expiry, renewal, fencing tokens and alias canonicalization.

[REQUIREMENT]
UID: TR-033
STATUS: Active
TITLE: TR-033 P0
STATEMENT: Multiple sessions, driver versions or clients cannot independently control the same physical resource.

[REQUIREMENT]
UID: TR-034
STATUS: Active
TITLE: TR-034 P1
STATEMENT: Device-specific policies: exclusive, safe shared read-only, exclusive controller with observers, host-sampled publish/subscribe.

[REQUIREMENT]
UID: TR-035
STATUS: Active
TITLE: TR-035 P1
STATEMENT: Observers receive host-produced measurements/logs, not arbitrary independent SCPI reads that could change state.

[REQUIREMENT]
UID: TR-036
STATUS: Active
TITLE: TR-036 P0
STATEMENT: Record host, manufacturer/model/firmware, driver/version/hash, instrument capability and calibration reference.

[REQUIREMENT]
UID: TR-037
STATUS: Active
TITLE: TR-037 P1
STATEMENT: Use official IVI class interfaces where available, SCPI/VISA otherwise, with vendor-specific optional capabilities. Provide optional read-only inspection of an operator-supplied IVI configuration snapshot through official shared components, retaining logical names, driver-session references, modules, resource descriptors and standard settings without creating vendor drivers or changing configuration. Acceptance: Distinguish identical GPIB addresses on separate controllers without requiring serial numbers; retain aliases and unresolved-reference diagnostics; reject malformed or oversized XML and external entities; leave saved setup unchanged; report an unsupported provider platform explicitly. Configuration inspection shall not imply hardware validation, lossless export, driver activation or IVI conformance. An explicit activation operation may open a saved DMM route only through a host-code registered typed provider approving its exact binding and current controller mapping. Acceptance: Reject stale or altered binding review before I/O; share canonical reservation contention across routes and direct clients; retain ownership after initialization, dispatch or cleanup failure; require successful provider-specific recovery before reuse; keep synchronous in-flight work owned despite caller cancellation. Registration batches shall be atomic and validate bounded binding metadata before publishing resources. DMM measurement requires successful explicit configuration. Optional expected identity checks shall use a registered provider reader, compare only supplied fields, keep serial optional, and quarantine mismatches after opening. Cached lease-scoped status shall not dispatch or wait for vendor I/O. Queued cancellation shall complete without dispatch or releasing an in-flight owner. The shared registry shall reject assigning a registered descriptor to a different canonical instrument even across provider-service instances. Providers shall declare permitted functions (DC voltage only when omitted), copied at registration and enforced before I/O. Runtime requests shall require explicit configuration fields and reject duplicate or unknown JSON fields. Successful readings shall atomically include function, base SI unit, requested range/resolution, pinned revision, per-activation sequence, host receipt time and a non-capability session correlation; concurrent reconfiguration shall not relabel earlier readings.

[REQUIREMENT]
UID: TR-038
STATUS: Active
TITLE: TR-038 P1
STATEMENT: Versioned protobuf/gRPC contracts with capability negotiation; never serialize arbitrary CLR objects over the network.

[REQUIREMENT]
UID: TR-039
STATUS: Active
TITLE: TR-039 P0
STATEMENT: Authentication, TLS for non-loopback, operation-level authorization, and no arbitrary untrusted code in privileged host.

[REQUIREMENT]
UID: TR-040
STATUS: Active
TITLE: TR-040 P2
STATEMENT: Optional signed content-addressed driver packages in isolated worker processes, with version coexistence but single physical reservation authority.

[REQUIREMENT]
UID: TR-041
STATUS: Active
TITLE: TR-041 P0
STATEMENT: Mock definition separates initialize/default state from each operation's state transition and measurement behavior.

[REQUIREMENT]
UID: TR-042
STATUS: Active
TITLE: TR-042 P0
STATEMENT: DMM voltage/resistance mode changes determine subsequent measurement quantity, behavior and validity.

[REQUIREMENT]
UID: TR-043
STATUS: Active
TITLE: TR-043 P0
STATEMENT: Mock outputs support constants, sequences, sine, seeded noise, state-dependent functions, injected faults and timeouts. Acceptance: Stateful and imported mocks expose copied finite sequences of one to 4096 canonical-unit readings, strict exhaustion or explicit hold-last mode, cached cursor status and explicit removal. Only successful mode-compatible scalar reads advance cursor and revision; faults, observed cancellation and invalid clocks do not consume values. Reset or model replacement clears affected sequences. Sine and composite models reject invalid or unrepresentable output. Acceptance: Sequence regressions cover mode checks, cancellation before and while waiting, invalid clocks, fault precedence, reset and model replacement, independent capabilities and instances, bounded enumeration, atomic failed replacement, excess parallel readers, captured reads, facade use and exact maximum length. Acceptance: Definition-driven SCPI mocks reject control characters and oversized metadata identities; ambiguous command matches fail before state or transcript mutation. Detached immutable transcript and canonical-unit reading snapshots are captured under the transaction lock. Explicit simulated reset restores declared defaults and clears history, and cancellation is observed before mutations. These APIs apply only to simulation and imply no physical device safety state. Acceptance: Stateful mock snapshots expose detached pending-fault counts and configured model kinds without exposing exception objects, callbacks or sequence values. Explicit bulk fault, sequence and behavior removal increments revision once only when something is removed and preserves unrelated state. Cancellation-aware reset shares the synchronous reset transaction, and observed cancellation after clock sampling preserves queued faults and sequences. Acceptance: Stateful mocks provide explicit opt-in scalar measurement preparation using the canonical run clock and an immutable indexed phase-latency sample. Reads before readiness, cancellation and failed output preserve preparation, sequence values and queued faults; readiness checks precede fault consumption. Only a successful scalar read consumes preparation, sharing one revision increment with sequence advancement. Actual mode changes and reset invalidate preparations; cached preparation status and explicit cancellation do not query time or hardware. Imported facades forward to the canonical engine. Existing unprepared reads and independently captured immutable acquisitions retain their documented behavior; automatic wall pacing and physical acquisition timing are not claimed.



[REQUIREMENT]
UID: TR-044
STATUS: Active
TITLE: TR-044 P1
STATEMENT: One explicit run-scoped shared simulation clock for all instruments and virtual DUT components.

[REQUIREMENT]
UID: TR-045
STATUS: Active
TITLE: TR-045 P1
STATEMENT: Real-time, accelerated, paused and manually advanced virtual-time modes; speed factor changes wall duration, not modeled physical dynamics. Acceptance: A run-scoped adjustable clock exposes manual, paused, real-time, accelerated and slowed modes using an injected monotonic provider. Speed changes preserve accumulated logical time and fractional ticks; invalid rates, negative manual advances, backwards provider time and overflow fail explicitly. The clock owns no timers or workers. Experiment composition selects one canonical clock per run and preserves the default manual API. Existing step-runner automatic pacing and UI controls remain unfinished integration work.


[REQUIREMENT]
UID: TR-046
STATUS: Active
TITLE: TR-046 P0
STATEMENT: Physical safety delays, lease expiry, authentication and real hardware timeouts never use accelerated virtual time. Acceptance: Adjustable simulation clock selection affects only simulation elapsed time; heartbeat expiry, host lease fencing, physical safety delays and physical I/O deadlines retain their existing real-time mechanisms.


[REQUIREMENT]
UID: TR-047
STATUS: Active
TITLE: TR-047 P1
STATEMENT: Model initialization/warmup, settling, integration, trigger/acquisition, processing latency, jitter and optional display pacing separately. Acceptance: A simulation-only latency profile separates initialization, settling, integration, trigger, acquisition, processing and display durations. Copied unique phase definitions enforce nonnegative durations and bounded symmetric jitter with an aggregate maximum of one logical day. Counter-based seeded integer-tick samples are reproducible by operation index independent of call or thread order. Samples are detached, expose phase and total durations, and reject invalid indices, negative start times and deadline overflow without creating workers or consulting physical clocks. Full instrument pacing and qualification remain open.

[REQUIREMENT]
UID: TR-048
STATUS: Active
TITLE: TR-048 P1
STATEMENT: Strict EasyMock-style expected sequences, unordered regions, cardinality, argument matchers, fault injection and cross-device partial-order expectations.

[REQUIREMENT]
UID: TR-049
STATUS: Active
TITLE: TR-049 P1
STATEMENT: Reproducible seeded randomness, virtual timestamps, state snapshots, deterministic scheduling and transcript replay. Acceptance: Mock snapshots capture detached read-only sequence positions with the state revision. Seeded noise draws serialize access to per-instance Random state, and interpolation remains finite across opposite finite double extremes. Composite membership is copied so later caller-array mutation does not rewire an active model. This is partial reproducibility support; full deterministic scheduling and transcript replay remain unfinished. Acceptance: Regression evidence compares concurrent seeded samples with an exact serial multiset, verifies invalid-time calls preserve random state, retains snapshot deconstruction compatibility and proves sequence/fault isolation across DI runs. Acceptance: An explicitly pumped simulation scheduler shares an injected run clock, owns no timers or workers, and never dispatches hardware or ownership commands. Bounded events are ordered by logical due time then acceptance identifier, with detached read-only snapshots, cancellation, clear and peek controls. Negative or backwards logical clocks, queue overflow and deadline overflow fail without consuming event identifiers or pending events. Concurrent operations serialize accepted order; this is not a claim that arbitrary racing thread order is reproducible or that full instrument transcript replay is complete. Acceptance: Standalone scalar simulation replay copies at most 4096 canonical immutable samples with bounded labels, finite values and nondecreasing nonnegative logical timestamps. A read consumes exactly one sample only for an exact ordinal mode/capability and timestamp match; rejection or observed cancellation preserves the cursor. Diagnostics, plan snapshots and remaining samples are detached and do not read time. Explicit reset and fork create reproducible local runs. Parallel reads serialize consumption without duplicates. Replay has no hardware, ownership, timer or worker authority; a transactional engine adapter, cross-device recording and full step-runner replay remain deferred.



[REQUIREMENT]
UID: TR-050
STATUS: Active
TITLE: TR-050 P2
STATEMENT: Virtual wiring/DUT transfer functions and validated noise/uncertainty models; never claim simulator calibration.

[REQUIREMENT]
UID: TR-051
STATUS: Active
TITLE: TR-051 P0
STATEMENT: UnitsNet quantities (volts, ohms, amperes, hertz, temperature, duration); reject dimension mismatches.

[REQUIREMENT]
UID: TR-052
STATUS: Active
TITLE: TR-052 P0
STATEMENT: Preserve DC/RMS/peak/Vpp, measurement mode, range, limits, resolution, quality, uncertainty and source metadata.

[REQUIREMENT]
UID: TR-053
STATUS: Active
TITLE: TR-053 P0
STATEMENT: Record acquisition timestamp, host wall time, simulation elapsed time if relevant, run/step IDs and driver identity.

[REQUIREMENT]
UID: TR-054
STATUS: Active
TITLE: TR-054 P0
STATEMENT: Raw readings and run events are append-only; redlines/corrections cannot rewrite original evidence.

[REQUIREMENT]
UID: TR-055
STATUS: Active
TITLE: TR-055 P1
STATEMENT: Durable local persistence (SQLite initially), checkpoints, crash recovery and transactional consistency.

[REQUIREMENT]
UID: TR-056
STATUS: Active
TITLE: TR-056 P1
STATEMENT: Persist procedure revision/hash, configuration, operator, equipment/calibration, measurement rows, outcomes, attachments and approvals.

[REQUIREMENT]
UID: TR-057
STATUS: Active
TITLE: TR-057 P1
STATEMENT: CSV/machine-readable export, tables, filtering, charts, waveform display, run comparison and reports.

[REQUIREMENT]
UID: TR-058
STATUS: Active
TITLE: TR-058 P1
STATEMENT: Operate without central database/network, then synchronize with stable IDs, conflict detection, duplicate suppression and explicit reconciliation.

[REQUIREMENT]
UID: TR-059
STATUS: Active
TITLE: TR-059 P1
STATEMENT: Hosts retain bounded event spools; reconnect replays available events with visible gap markers.

[REQUIREMENT]
UID: TR-060
STATUS: Active
TITLE: TR-060 P1
STATEMENT: Pass/fail/limits calculations are separate traceable results, never substituted for original measured values.

[REQUIREMENT]
UID: TR-061
STATUS: Active
TITLE: TR-061 P0
STATEMENT: Execution-scoped redlines include before/after, rationale, author, timestamp, review state and affected steps.

[REQUIREMENT]
UID: TR-062
STATUS: Active
TITLE: TR-062 P0
STATEMENT: Reviewers approve/reject/request changes; released procedure definitions remain immutable.

[REQUIREMENT]
UID: TR-063
STATUS: Active
TITLE: TR-063 P0
STATEMENT: Attributable electronic signatures at step, hold point, section and final run with explicit signing intent.

[REQUIREMENT]
UID: TR-064
STATUS: Active
TITLE: TR-064 P0
STATEMENT: Signatures bind signer identity/role, timestamp and exact content hash; post-sign changes require new attestation.

[REQUIREMENT]
UID: TR-065
STATUS: Active
TITLE: TR-065 P1
STATEMENT: Role-based permissions for author, operator, reviewer, approver and administrator, including optional separation of duties.

[REQUIREMENT]
UID: TR-066
STATUS: Active
TITLE: TR-066 P1
STATEMENT: Corrections after submission remain possible only as logged attributable changes/superseding records.

[REQUIREMENT]
UID: TR-067
STATUS: Active
TITLE: TR-067 P1
STATEMENT: Deviations/nonconformances, disposition, follow-up actions and operator notes/photos/files link to stable step IDs.

[REQUIREMENT]
UID: TR-068
STATUS: Active
TITLE: TR-068 P0
STATEMENT: No 21 CFR Part 11 or other regulatory compliance claim without dedicated validation of identity, signatures, retention and audit controls.

[REQUIREMENT]
UID: TR-069
STATUS: Active
TITLE: TR-069 P0
STATEMENT: One browser workspace composes, inserts, executes, redlines, reviews and signs off steps; notebook not required.

[REQUIREMENT]
UID: TR-070
STATUS: Active
TITLE: TR-070 P0
STATEMENT: Inline measurement values, limits, pass/fail, logs, operator prompts and step progress; minimal presses.

[REQUIREMENT]
UID: TR-071
STATUS: Active
TITLE: TR-071 P1
STATEMENT: Easy pre-submit correction, logged post-submit changes, clear confirmations for destructive or hazardous operations.

[REQUIREMENT]
UID: TR-072
STATUS: Active
TITLE: TR-072 P1
STATEMENT: Host and client show the same authorized log events with event IDs, step/run correlation, filters and replay.

[REQUIREMENT]
UID: TR-073
STATUS: Active
TITLE: TR-073 P1
STATEMENT: Live graphs, waveform plots, sortable measurement tables and time axes with correct units.

[REQUIREMENT]
UID: TR-074
STATUS: Active
TITLE: TR-074 P1
STATEMENT: Accessible responsive layout, keyboard support, navigation/search and persistent unsaved editing state.

[REQUIREMENT]
UID: TR-075
STATUS: Active
TITLE: TR-075 P2
STATEMENT: Optional Monaco-backed C# or structured step editing without coupling procedure storage to a particular editor.

[REQUIREMENT]
UID: TR-076
STATUS: Active
TITLE: TR-076 P0
STATEMENT: Microsoft.Extensions.Logging structured events for commands, leases, runs, steps, results, approvals, faults and cleanup. Setup shall log inspection, reviewed binding changes, discovery, validation and save outcomes using stable event IDs and structured fields. Acceptance: Capture success and failure events including saved revision and diagnostic categories; exclude XML, driver option values, resource descriptors and exception message payloads from application logs. Typed IVI lifecycle events shall identify canonical resource, a session correlation distinct from its lease token, configuration revision, operation name, completion duration in milliseconds and stable preflight rejection reasons. Acceptance: Log configure/measure starts and completions and identity failures without lease capabilities, measured values, identity values or vendor exception messages. Diagnostic sink exceptions in canonical registry and typed IVI lifecycle logging shall not change ownership, replay I/O or turn successful cleanup into failure. Count and expose those logging failures through cached diagnostics. Record cleanup/recovery starts and completion durations and retain a payload-free last-failure phase in session status. Durable ownership logging shall distinguish persistence, startup quarantine, reconciliation dispatch, provider failure and durable acknowledgment using non-capability record IDs. Acceptance: Capture these outcomes without journal paths, raw routes, lease tokens or exception messages; a logging failure shall not alter ownership. Shutdown and heartbeat diagnostics shall distinguish admission stop, cleanup start, per-resource completion, decision deadline, pending workers, suspect ownership and permanent expiry. Acceptance: Use stable structured events without lease capabilities or provider messages; failing sinks cannot alter renewal, fencing or cleanup results. Acceptance: A throwing SCPI diagnostic sink shall preserve successful return values, original instrument exceptions and exactly-once I/O. Acceptance: Throwing or null-returning SCPI redactors shall substitute redaction markers without exposing payloads or affecting I/O. Acceptance: SCPI failure logs shall record exception type without forwarding exception objects or provider messages; callers shall retain the original exception. Acceptance: Mock logging sink exceptions shall not alter mode selection, queued fault delivery or reset; expose a monotonic diagnostic failure count. Acceptance: Scalar and captured mock fault logs shall record error type without exception objects or injected exception messages. Acceptance: Setup discovery, validation, successful saves and rejected saves retain their original outcomes when diagnostic sinks throw; a monotonic cached failure count records those sink failures without provider message payloads. Acceptance: A regression shall use a throwing setup logger across discovery, validation, successful persistence and revision rejection; the saved revision and original conflict remain observable and diagnostic failures are counted. Acceptance: SCPI diagnostics expose monotonic sink and redactor failure counts, preserve exact I/O outcomes, bound opted-in payload prefixes without splitting surrogate pairs, reject control-bearing or over-128-character display names, and emit stable event IDs 7600/7601/7602. IVI catalog inspection and draft application preserve original outcomes under throwing sinks and expose a cached failure count. Acceptance: Focused IVI catalog regressions preserve successful detached inspection, exact original reader errors and draft-rejection errors when every diagnostic event throws. Acceptance: Experiment runner logging isolates write, enabled, scope creation and scope disposal failures and exposes a monotonic failure count. Procedure context uses the same isolated logger. Stable events 7700 through 7705 omit exception objects and provider messages while callers retain original errors. Diagnostic failures cannot suppress cleanup, alter recovery fencing or publish a different terminal outcome.











[REQUIREMENT]
UID: TR-077
STATUS: Active
TITLE: TR-077 P1
STATEMENT: OpenTelemetry traces/metrics propagate host, instrument, run, step and request correlations.

[REQUIREMENT]
UID: TR-078
STATUS: Active
TITLE: TR-078 P0
STATEMENT: Redact sensitive SCPI payloads by default; privileged debugging requires policy and retention controls.

[REQUIREMENT]
UID: TR-079
STATUS: Active
TITLE: TR-079 P0
STATEMENT: Slow log subscribers cannot block instrument I/O; critical alarms preserved with explicit loss/gap reporting.

[REQUIREMENT]
UID: TR-080
STATUS: Active
TITLE: TR-080 P0
STATEMENT: User-supplied C# runs in a restricted worker, not the privileged instrument host; host permissions remain authoritative.

[REQUIREMENT]
UID: TR-081
STATUS: Active
TITLE: TR-081 P1
STATEMENT: Audit retention, encryption, backup, trace IDs, clock discipline and tamper-evidence policy are documented and tested.

[REQUIREMENT]
UID: TR-082
STATUS: Active
TITLE: TR-082 P0
STATEMENT: Reproducible cross-platform build and hardware-free CI; actual VISA/IVI tests opt-in.

[REQUIREMENT]
UID: TR-083
STATUS: Active
TITLE: TR-083 P0
STATEMENT: Test startup failure, cancellation before/after dispatch, timeouts, cleanup failure and uncertain hardware state.

[REQUIREMENT]
UID: TR-084
STATUS: Active
TITLE: TR-084 P0
STATEMENT: Test lease conflicts, multi-instrument deadlock prevention, shared observers and mixed client/host versions.

[REQUIREMENT]
UID: TR-085
STATUS: Active
TITLE: TR-085 P1
STATEMENT: Test redlines, approval, signature hashes, offline conflicts and immutable execution records.

[REQUIREMENT]
UID: TR-086
STATUS: Active
TITLE: TR-086 P1
STATEMENT: Test deterministic mock timing, scaling, state transitions, noise seeds and partial-order expectations.

[REQUIREMENT]
UID: TR-087
STATUS: Active
TITLE: TR-087 P1
STATEMENT: Test host restart, disconnect, stale fencing tokens, log replay and unauthorized commands.

[REQUIREMENT]
UID: TR-088
STATUS: Active
TITLE: TR-088 P1
STATEMENT: End-to-end frequency sweep spanning two simulated hosts: reserve, configure, acquire, stream, plot, log, cancel and cleanup.

[REQUIREMENT]
UID: TR-089
STATUS: Active
TITLE: TR-089 P1
STATEMENT: Six-step electronic procedure demonstration: insert/reorder, execute, redline, approve, sign off and archive.

[REQUIREMENT]
UID: TR-090
STATUS: Active
TITLE: TR-090 P2
STATEMENT: Repeat same compiled procedure with approved physical drivers; compare semantic behavior, not identical SCPI transcripts.

[REQUIREMENT]
UID: BD-UOM-001
STATUS: Active
TITLE: BD-UOM-001 P0
STATEMENT: The unattended monitor shall raise exactly one overcurrent alarm when measured current first exceeds its configured threshold.

[REQUIREMENT]
UID: BD-UOM-002
STATUS: Active
TITLE: BD-UOM-002 P0
STATEMENT: The monitor shall evaluate alarms independently of browser graphics and external notification delivery.

[REQUIREMENT]
UID: BD-UOM-003
STATUS: Active
TITLE: BD-UOM-003 P0
STATEMENT: The demo shall label email and SMS events simulated and shall not contact real operators.

[REQUIREMENT]
UID: BD-UOM-004
STATUS: Active
TITLE: BD-UOM-004 P1
STATEMENT: The browser monitor shall plot measured current and a threshold, supporting start pause reset and fault injection.

[REQUIREMENT]
UID: BD-UOM-005
STATUS: Active
TITLE: BD-UOM-005 P1
STATEMENT: The browser monitor shall consume the same backend measurement events as the C# runner rather than duplicating the simulation.

[REQUIREMENT]
UID: BD-UOM-006
STATUS: Active
TITLE: BD-UOM-006 P1
STATEMENT: Browser acceptance tests shall verify chart elements alarm text reset and accessible status under Chromium.

[REQUIREMENT]
UID: BD-UOM-007
STATUS: Active
TITLE: BD-UOM-007 P0
STATEMENT: Actual hardware safe-state actions shall be independent of the browser and email or SMS delivery.

[REQUIREMENT]
UID: BD-UOM-008
STATUS: Active
TITLE: BD-UOM-008 P1
STATEMENT: Notification delivery shall use a durable outbox with idempotent retries receipts and escalation.

[REQUIREMENT]
UID: BD-TS-001
STATUS: Active
TITLE: BD-TS-001 P0
STATEMENT: Measurements shall be recorded in a local durable SQLite database without central network access.

[REQUIREMENT]
UID: BD-TS-002
STATUS: Active
TITLE: BD-TS-002 P0
STATEMENT: Stored quantities shall retain canonical UnitsNet dimensions and reject incompatible signal values.

[REQUIREMENT]
UID: BD-TS-003
STATUS: Active
TITLE: BD-TS-003 P0
STATEMENT: Batch writes shall be atomic and replay of the same sample identity shall not duplicate evidence.

[REQUIREMENT]
UID: BD-TS-004
STATUS: Active
TITLE: BD-TS-004 P1
STATEMENT: Queries shall support real UTC and accelerated simulated elapsed time independently.

[REQUIREMENT]
UID: BD-TS-005
STATUS: Active
TITLE: BD-TS-005 P1
STATEMENT: A background replicator shall synchronize local measurements to PostgreSQL or TimescaleDB after outages.

[REQUIREMENT]
UID: BD-TS-006
STATUS: Active
TITLE: BD-TS-006 P1
STATEMENT: Plot downsampling shall preserve peak excursions and raw acceptance evidence.

[REQUIREMENT]
UID: BD-SIM-001
STATUS: Active
TITLE: BD-SIM-001 P0
STATEMENT: Instrument mocks shall accept injected behavior and a run-scoped simulation clock. Acceptance: Captured meter reads shall reject missing acquisition components, empty or mismatched correlation IDs and mismatched meter/waveform start times before consuming queued faults; a subsequent valid read shall consume the fault exactly once. Acceptance: AutoMock shall reject negative maximum voltage conditions and nonfinite or negative unmatched baseline currents just as it rejects invalid rule results. Acceptance: A model that returns after its measurement token is cancelled shall not publish a successful scalar reading. Acceptance: Consuming a scalar or captured one-shot fault shall advance the mock state revision exactly once. Acceptance: Clearing pending faults shall return their count, preserve mode and overrides, and leave revision unchanged when already empty. Acceptance: Removing absent synchronous or asynchronous mock models shall not advance the state revision. Acceptance: Setting an already installed identical scalar override shall not advance the state revision. Acceptance: Each capability shall reject more than 256 pending injected faults without changing the queue or revision. Acceptance: A ramp between opposite finite double extremes shall produce a finite midpoint and retain clamped endpoints. Acceptance: Parsed capability mode lists shall reject mutation and preserve the validated operating-mode contract. Acceptance: Imported driver, mode and capability identifiers shall reject trailing newline characters rather than matching a valid prefix. Acceptance: Imported definition JSON shall reject more than 1 Mi characters or 32 nesting levels before instrument construction. Acceptance: Repeated JSON fields at any imported definition depth shall be rejected instead of silently replacing earlier values. Acceptance: Distinct imported mode identifiers shall not share the same case-insensitive SCPI selection command. Acceptance: Capabilities sharing an operating mode shall not bind the same case-insensitive query to different scalar metadata. Acceptance: Imported capabilities shall reject duplicate operating-mode references. Acceptance: A present mock default shall be numeric or explicit null; malformed strings and booleans shall not silently remove the fallback. Acceptance: AutoMock JSON shall reject repeated keys case-insensitively at every object depth and limit nesting to sixteen levels. Acceptance: Every JSON AutoMock action shall provide an explicit numeric value rather than inheriting the CLR zero default. Acceptance: Rule JSON shall reject numeric enum aliases while retaining case-insensitive symbolic action names. Acceptance: Fluent AutoMock builders shall reject more than 256 rules without mutating their accepted rule set. Acceptance: Builder, rule hashing and load decorator boundaries shall report ArgumentNullException for null rule entries. Acceptance: Rule hashing shall reject duplicate rule names consistently with builders and evaluators. Acceptance: Behaviorally identical positive and negative zero scalar rule values and voltage bounds shall produce the same rule fingerprint. Acceptance: Definition-driven SCPI mocks reject null or excessive metadata, blank/oversized templates, duplicate query or setter patterns, repeated placeholders, trailing input and oversized commands before state mutation; overflowing channels produce a range error. AutoMock decorator and fingerprint construction consume at most 257 entries and reject over 256 rules; condition matching rejects nonfinite voltage or negative elapsed time. Mode-aware callbacks reject nonfinite output and cannot publish success after cancellation; identical stateful model delegate installation preserves revision. Acceptance: Focused application regressions exercise SCPI rejection without state mutation, bounded metadata/rule enumeration, model cancellation and nonfinite output, idempotent delegate installation, and 64 parallel writes preserving channel isolation. Acceptance: Finite stored UnitsNet values that overflow conversion to a canonical base unit must be rejected: condition matching reports an argument-range error and mode-aware measurements report an invalid reading without leaking the transaction gate. Acceptance: Typed mocks validate canonical base-unit readings and honor cancellation after callbacks. Typed meters and supplies reject missing injected dependencies at construction. Negative run-clock timestamps fail before invoking behaviors or consuming stateful one-shot faults; failures leave transaction gates usable for subsequent valid reads.




























[REQUIREMENT]
UID: BD-SIM-002
STATUS: Active
TITLE: BD-SIM-002 P1
STATEMENT: Virtual thermal sensor output shall lag chamber setpoint with configurable time constant.

[REQUIREMENT]
UID: BD-SIM-003
STATUS: Active
TITLE: BD-SIM-003 P1
STATEMENT: Virtual wiring shall reject incompatible connections missing sources duplicate drivers and cycles.

[REQUIREMENT]
UID: BD-SIM-004
STATUS: Active
TITLE: BD-SIM-004 P1
STATEMENT: Approved custom C# mock behavior shall compile with Roslyn and run in isolated unprivileged workers.

[REQUIREMENT]
UID: BD-SIM-005
STATUS: Active
TITLE: BD-SIM-005 P1
STATEMENT: The thermal demo shall record chamber setpoint sensor temperature and supply current to SQLite.

[REQUIREMENT]
UID: BD-SIM-006
STATUS: Active
TITLE: BD-SIM-006 P1
STATEMENT: The thermal demo shall display 30 to 70 to minus 30 to 30 degree cycling with two-hour hot and cold dwells.

[REQUIREMENT]
UID: BD-REQ-001
STATUS: Active
TITLE: BD-REQ-001 P0
STATEMENT: Requirements shall have unique stable IDs and shall be maintained in parseable version-controlled StrictDoc source.

[REQUIREMENT]
UID: BD-REQ-002
STATUS: Active
TITLE: BD-REQ-002 P0
STATEMENT: Every requirement shall have an explicit verification status and a trace to implementation tests and/or open GitHub work.

[REQUIREMENT]
UID: BD-REQ-003
STATUS: Active
TITLE: BD-REQ-003 P0
STATEMENT: CI shall validate requirements syntax identifiers and traceability and fail for broken references. Acceptance: The C# requirement gate shall preserve reference diagnostics, exit codes and audit checks, with deterministic worker ordering and measured end-to-end implementation selection. Acceptance: The complete check workflow shall include fresh-shell startup, tooling builds and focused regressions in cold-artifact and cached timings; a content-validated managed build cache shall reject changed inputs and missing outputs without caching check results.



[REQUIREMENT]
UID: BD-REQ-004
STATUS: Active
TITLE: BD-REQ-004 P1
STATEMENT: The requirements report shall distinguish committed source from successful test execution and verified behavior.

[REQUIREMENT]
UID: BD-REQ-005
STATUS: Active
TITLE: BD-REQ-005 P1
STATEMENT: Acceptance scenarios shall be executable in Reqnroll with xUnit and requirement ID tags.

[REQUIREMENT]
UID: BD-BUILD-001
STATUS: Active
TITLE: BD-BUILD-001 P0
STATEMENT: The project shall restore build and run its hardware-free tests on Windows macOS and Linux.

[REQUIREMENT]
UID: BD-BUILD-002
STATUS: Active
TITLE: BD-BUILD-002 P0
STATEMENT: A new computer shall be able to provision supported .NET SDK and documentation tools using documented setup scripts.

[REQUIREMENT]
UID: BD-BUILD-003
STATUS: Active
TITLE: BD-BUILD-003 P1
STATEMENT: Dependency versions and reproducible restore shall be governed by central version policy and lockfiles.

[REQUIREMENT]
UID: BD-BUILD-004
STATUS: Active
TITLE: BD-BUILD-004 P1
STATEMENT: CI shall test browser controls and plots using an automated real browser and preserve failure artifacts.

[REQUIREMENT]
UID: BD-DOC-001
STATUS: Active
TITLE: BD-DOC-001 P0
STATEMENT: The repository shall maintain a software development plan architecture description requirements and user manual.

[REQUIREMENT]
UID: BD-DOC-002
STATUS: Active
TITLE: BD-DOC-002 P1
STATEMENT: The project shall provide an interactive HTML overview of architecture examples and feature status.

[REQUIREMENT]
UID: BD-WASM-001
STATUS: Active
TITLE: BD-WASM-001 P2
STATEMENT: A browser demonstration shall execute selected C# simulation code via WebAssembly without privileged hardware access.

[REQUIREMENT]
UID: BD-EXP-001
STATUS: Active
TITLE: BD-EXP-001 P0
STATEMENT: An immutable experiment definition shall register uniquely named typed instrument roles and backend choices. Acceptance: Public experiment and run role metadata shall reject list mutation and preserve frozen typed registrations.


[REQUIREMENT]
UID: BD-EXP-002
STATUS: Active
TITLE: BD-EXP-002 P0
STATEMENT: Each experiment run shall create and dispose isolated DI scope, simulation clock and stateful mock instances. Acceptance: Explicit clock selection replaces both default manual and canonical interface registrations; one scoped interface is shared by instrument models. Repeated selection and reserved-service replacement fail before composition changes. Eager startup resolves the clock before roles and cleans up dependencies if its factory fails or returns null; the default manual Clock property stays compatible.


[REQUIREMENT]
UID: BD-EXP-003
STATUS: Active
TITLE: BD-EXP-003 P1
STATEMENT: Experiment mock behaviors shall receive typed dependencies through constructor injection including keyed instrument roles. Acceptance: Eager startup shall reject a null-returning instrument factory with a role-specific error and perform normal failed-start cleanup. Acceptance: Duplicate unkeyed behavior or model registrations and replacement of the canonical run clock shall fail at composition before a run starts. Acceptance: Unkeyed AutoMock registration shall reject an existing load dependency before running configuration callbacks or replacing run services. Acceptance: Rule-configuration callbacks cannot reenter or freeze the outer experiment builder; a failed callback leaves it reusable. Null AutoMock baseline factories report explicit composition errors, including the role for keyed loads. Experiment names, role names and host names reject controls and lengths over 128 characters before registration. Acceptance: Focused integration regressions cover callback rollback, all reentrant registration paths, keyed and unkeyed null baseline cleanup, exact name bounds, shared run-scoped model/clock identity, sixteen parallel runs, null model fail-fast behavior and cancellation during baseline construction.






[REQUIREMENT]
UID: BD-EXP-004
STATUS: Active
TITLE: BD-EXP-004 P0
STATEMENT: Physical instrument resolution shall use authenticated host discovery and host-owned fenced reservations, never DI alone.

[REQUIREMENT]
UID: BD-EXP-005
STATUS: Active
TITLE: BD-EXP-005 P1
STATEMENT: Experiment start and disposal shall record resource provenance and recover safely after partial initialization failures. Acceptance: Async simulated startup shall resolve every registered role before returning; factory failure or cancellation shall await disposal of DI-owned resources. Startup and cleanup failures shall both remain observable, and provider cleanup shall be attempted after a scope disposal failure. Physical recovery and durable provenance remain separate acceptance work. Concurrent and repeated session disposal calls shall share one cleanup completion and retain cleanup failures; new instrument and clock access shall be rejected after cleanup starts.

[REQUIREMENT]
UID: BD-DASH-001
STATUS: Active
TITLE: BD-DASH-001 P1
STATEMENT: The host shall expose a read-only instrument registry dashboard showing instrument class backend host and lease state.

[REQUIREMENT]
UID: BD-DASH-002
STATUS: Active
TITLE: BD-DASH-002 P1
STATEMENT: Each instrument dashboard panel shall show a bounded recent activity log without sensitive command payloads.

[REQUIREMENT]
UID: BD-DASH-003
STATUS: Active
TITLE: BD-DASH-003 P1
STATEMENT: The HTML dashboard shall refresh local host status and report connectivity failures without implying live data when disconnected.

[REQUIREMENT]
UID: BD-DASH-004
STATUS: Active
TITLE: BD-DASH-004 P0
STATEMENT: Remote multi-host dashboard access shall require authentication authorization TLS and privacy-preserving telemetry.

[REQUIREMENT]
UID: BD-DASH-005
STATUS: Active
TITLE: BD-DASH-005 P1
STATEMENT: The dashboard shall aggregate experiment roles and instruments across authorized hosts with stale heartbeat indication.

[REQUIREMENT]
UID: BD-DASH-006
STATUS: Active
TITLE: BD-DASH-006 P1
STATEMENT: Browser acceptance tests shall verify registered instruments reservation transitions log rendering and disconnected states.

[REQUIREMENT]
UID: BD-VERSION-001
STATUS: Active
TITLE: BD-VERSION-001 P0
STATEMENT: Experiment definitions and behavior packages shall have stable revisions and hashes stored in the run manifest.

[REQUIREMENT]
UID: BD-VERSION-002
STATUS: Active
TITLE: BD-VERSION-002 P1
STATEMENT: Host protocol and instrument driver compatibility shall be negotiated across client/server versions.

[REQUIREMENT]
UID: BD-VERSION-003
STATUS: Active
TITLE: BD-VERSION-003 P1
STATEMENT: Development documentation shall explain Git branches commits tags semantic versioning and reproducible experiment revisions.

[REQUIREMENT]
UID: BD-VERSION-004
STATUS: Active
TITLE: BD-VERSION-004 P0
STATEMENT: Reproducible runs shall pin behavior dependencies, model configuration and simulation seeds.

[REQUIREMENT]
UID: BD-PARITY-001
STATUS: Active
TITLE: BD-PARITY-001 P1
STATEMENT: Competitor comparison shall distinguish shipped tested functionality from prototypes and planned features.

[REQUIREMENT]
UID: BD-AM-001
STATUS: Active
TITLE: BD-AM-001 P0
STATEMENT: An experiment shall inject declarative AutoMock rules into a typed instrument behavior without changing instrument driver source.

[REQUIREMENT]
UID: BD-AM-002
STATUS: Active
TITLE: BD-AM-002 P0
STATEMENT: AutoMock shall support virtual-time activation, voltage-range predicates, fixed values, baseline scaling and deterministic priority.

[REQUIREMENT]
UID: BD-AM-003
STATUS: Active
TITLE: BD-AM-003 P0
STATEMENT: Rule configurations shall reject invalid values, duplicate names, unsupported actions and incompatible schema versions before execution.

[REQUIREMENT]
UID: BD-AM-004
STATUS: Active
TITLE: BD-AM-004 P1
STATEMENT: An experiment shall load data-only AutoMock rules from a versioned JSON file without executing expressions or user code.

[REQUIREMENT]
UID: BD-AM-005
STATUS: Active
TITLE: BD-AM-005 P0
STATEMENT: AutoMock shall preserve instrument state invariants including zero output current when simulated output is disabled.

[REQUIREMENT]
UID: BD-AM-006
STATUS: Active
TITLE: BD-AM-006 P1
STATEMENT: Experiment run metadata shall expose a stable SHA-256 of its AutoMock rule set for reproducibility.

[REQUIREMENT]
UID: BD-AM-007
STATUS: Active
TITLE: BD-AM-007 P1
STATEMENT: The AutoMock framework shall support typed command and mode-dependent behavior for DMM, generator, SMU and chamber instrument classes.

[REQUIREMENT]
UID: BD-AM-008
STATUS: Active
TITLE: BD-AM-008 P1
STATEMENT: Advanced rules shall be supported through an optional evaluated rule engine adapter without adding an expression engine to the core.

[REQUIREMENT]
UID: BD-AM-009
STATUS: Active
TITLE: BD-AM-009 P0
STATEMENT: Untrusted executable mock behavior shall run only in isolated unprivileged simulation workers with approved package versions.

[REQUIREMENT]
UID: BD-AM-010
STATUS: Active
TITLE: BD-AM-010 P1
STATEMENT: An integrated experiment shall exercise AutoMock, virtual time, monitoring, persistence and dashboard telemetry through the same C# backend.

[REQUIREMENT]
UID: BD-AM-011
STATUS: Active
TITLE: BD-AM-011 P1
STATEMENT: AutoMock shall generate typed default simulation adapters from instrument definitions so developers configure overrides without duplicating command boilerplate.

[REQUIREMENT]
UID: BD-AM-012
STATUS: Active
TITLE: BD-AM-012 P1
STATEMENT: Multiple named instruments in one experiment shall support independently keyed AutoMock behaviors and distinct rule-set fingerprints.

[REQUIREMENT]
UID: BD-AM-013
STATUS: Active
TITLE: BD-AM-013 P0
STATEMENT: Generic mock measurements shall return the explicitly requested UnitsNet quantity type and reject unregistered quantity capabilities.

[REQUIREMENT]
UID: BD-AM-014
STATUS: Active
TITLE: BD-AM-014 P0
STATEMENT: A generic quantity request shall not implicitly change an instrument's configured measurement mode.

[REQUIREMENT]
UID: BD-AM-015
STATUS: Active
TITLE: BD-AM-015 P1
STATEMENT: Instrument definitions shall provide the supported quantity capabilities and units for generated default mocks rather than relying on return-type inference.

[REQUIREMENT]
UID: BD-AM-016
STATUS: Active
TITLE: BD-AM-016 P1
STATEMENT: Typed measurement mock behaviors shall support deterministic experiment-clock-indexed values and explicit constant defaults.

[REQUIREMENT]
UID: BD-DSL-001
STATUS: Active
TITLE: BD-DSL-001 P1
STATEMENT: The test framework shall provide a separate optional Parlot-based procedure parsing project with no parser dependency in the instrument core.

[REQUIREMENT]
UID: BD-DSL-002
STATUS: Active
TITLE: BD-DSL-002 P0
STATEMENT: Procedure text shall parse into a typed AST with line-addressable syntax diagnostics and shall reject unsupported statements.

[REQUIREMENT]
UID: BD-DSL-003
STATUS: Active
TITLE: BD-DSL-003 P0
STATEMENT: Procedure validation shall reject unknown instrument roles, incompatible measurement modes and physical units, and undefined variables before execution.

[REQUIREMENT]
UID: BD-DSL-004
STATUS: Active
TITLE: BD-DSL-004 P1
STATEMENT: A mock-only procedure shall execute against registered typed instrument mocks through the existing experiment runner and virtual clock.

[REQUIREMENT]
UID: BD-DSL-005
STATUS: Active
TITLE: BD-DSL-005 P1
STATEMENT: Procedure measurements and limit assertions shall preserve UnitsNet dimensions and produce attributable result records.

[REQUIREMENT]
UID: BD-DSL-006
STATUS: Active
TITLE: BD-DSL-006 P1
STATEMENT: The procedure editor and text DSL shall share stable step IDs, revision history and comment-preserving round-trip representation.

[REQUIREMENT]
UID: BD-DSL-007
STATUS: Active
TITLE: BD-DSL-007 P0
STATEMENT: The DSL shall not permit arbitrary code or physical instrument control without explicit authorization, capability checks and safe-state handling.

[REQUIREMENT]
UID: BD-GEN-001
STATUS: Active
TITLE: BD-GEN-001 P0
STATEMENT: The instrument generator shall emit a strongly typed UnitsNet driver and matching simulated SCPI transport from the same validated definition.

[REQUIREMENT]
UID: BD-GEN-002
STATUS: Active
TITLE: BD-GEN-002 P0
STATEMENT: Generated mocks shall enforce declared command templates, supported channel bounds and finite parameter ranges without arbitrary commands.

[REQUIREMENT]
UID: BD-GEN-003
STATUS: Active
TITLE: BD-GEN-003 P1
STATEMENT: Generated mocks shall support per-channel state and strongly typed simulated reading overrides without changing the generated driver API. Acceptance: Generated preview source explicitly enables nullable analysis. Generated scalar mock behavior results must be finite in canonical units, observe cancellation before and after callbacks, retain mode gating and preserve explicit reading state after failures. Nonfinite behavior results fail without publishing a reading; callbacks remain caller supplied and simulation only.


[REQUIREMENT]
UID: BD-GEN-004
STATUS: Active
TITLE: BD-GEN-004 P0
STATEMENT: Instrument inventory shall distinguish external instrument source catalog entries from completed driver ports and physical hardware validation.

[REQUIREMENT]
UID: BD-GEN-005
STATUS: Active
TITLE: BD-GEN-005 P1
STATEMENT: The build shall verify checked-in generated driver/mock source against definitions without rewriting it.

[REQUIREMENT]
UID: BD-GEN-006
STATUS: Active
TITLE: BD-GEN-006 P0
STATEMENT: Keithley 236 source-mode changes shall invalidate old compliance and bias configuration and prevent unsafe OPERATE requests.

[REQUIREMENT]
UID: BD-DEF-001
STATUS: Active
TITLE: BD-DEF-001 P0
STATEMENT: Instrument definitions shall have a versioned machine-readable schema describing identity, source provenance, capabilities, methods, modes, mock models and review state.

[REQUIREMENT]
UID: BD-DEF-002
STATUS: Active
TITLE: BD-DEF-002 P1
STATEMENT: Instrument Definer shall extract external instrument source descriptors and public methods using static parsing without executing upstream Python source.

[REQUIREMENT]
UID: BD-DEF-003
STATUS: Active
TITLE: BD-DEF-003 P1
STATEMENT: Instrument Definer shall accept spreadsheet-exported properties and methods CSV files and preserve explicit quantities, modes, commands and source references.

[REQUIREMENT]
UID: BD-DEF-004
STATUS: Active
TITLE: BD-DEF-004 P0
STATEMENT: Instrument Definer shall reject duplicate or invalid identifiers, incompatible physical units, invalid ranges and unsafe unsupported validation claims.

[REQUIREMENT]
UID: BD-DEF-005
STATUS: Active
TITLE: BD-DEF-005 P0
STATEMENT: Extracted definitions shall remain unreviewed and shall not be promoted to physical hardware drivers without source/manual and safety review evidence.

[REQUIREMENT]
UID: BD-DEF-006
STATUS: Active
TITLE: BD-DEF-006 P0
STATEMENT: A schema-v2 definition shall support a simulated mode-aware UnitsNet mock preview with strict quantity/mode validation and no physical access.

[REQUIREMENT]
UID: BD-DEF-007
STATUS: Active
TITLE: BD-DEF-007 P1
STATEMENT: Reviewed schema-v2 definitions shall generate typed asynchronous driver and mode-aware mock source with lifecycle, unit and command validation.

[REQUIREMENT]
UID: BD-DEF-008
STATUS: Active
TITLE: BD-DEF-008 P1
STATEMENT: external instrument source extraction shall report inherited/dynamic methods, parser coverage and unresolved mappings before a definition can be reviewed.

[REQUIREMENT]
UID: BD-LIFE-001
STATUS: Active
TITLE: Register before I/O P0
STATEMENT: Every framework-managed open shall register its canonical resource and Opening state before initialization I/O and retain an accountable cleanup owner. Acceptance: Inject failure at every open stage; registry contains no unowned live session. Registration of a provider batch shall reject all entries on a canonical ID conflict or malformed binding without partially publishing instruments or performing I/O. Registered physical DMM grants shall persist unresolved ownership before returning a lease or dispatching a factory. Acceptance: A journal write failure prevents initialization and new ownership; faulted persistence cannot silently fall back to memory.

[REQUIREMENT]
UID: BD-LIFE-002
STATUS: Active
TITLE: Lifecycle transitions P0
STATEMENT: The registry shall enforce and log allowed Opening, Ready, Busy, Closing, Closed, Faulted and RecoveryRequired transitions with run and resource identity. Acceptance: Exercise legal and illegal transitions, including concurrent open/close; reject illegal transitions.

[REQUIREMENT]
UID: BD-LIFE-003
STATUS: Active
TITLE: Partial startup rollback P0
STATEMENT: Partial startup failure shall clean up all acquired resources in declared dependency-safe order and preserve primary and cleanup errors. Acceptance: Fail the second of three opens; first is cleaned, third is not opened, and all errors remain attributable.

[REQUIREMENT]
UID: BD-LIFE-004
STATUS: Active
TITLE: Bounded shutdown P0
STATEMENT: Shutdown shall stop new work and execute declared device-specific abort, safe-state confirmation and close using deadlines independent of run cancellation. Acceptance: Cancel a run then hang one cleanup; shutdown decisions remain bounded and other resources still receive cleanup. For registered DMMs, an irreversible admission stop shall reject new grants and queued command dispatch; concurrent shutdown callers shall share one cleanup attempt and report. Use finite host-owned wait and worker budgets independent of request cancellation. Require an explicitly registered safe-state preparation callback before closing live sessions. Acceptance: With one blocked provider, another worker can clean a different resource; timeout retains unresolved evidence and reports pending work without declaring safe state. Never dispatch queued cleanup after its deadline or replay successful preparation through repeated shutdown calls. Keep bounded decision outcomes immutable while separately exposing late worker completion.

[REQUIREMENT]
UID: BD-LIFE-005
STATUS: Active
TITLE: Recovery quarantine P0
STATEMENT: Unconfirmed shutdown shall retain RecoveryRequired ownership quarantine until an authorized recorded reconciliation confirms that reuse is permitted. Acceptance: Lose cleanup acknowledgment; reject a new reservation until explicit recovery completes. Cancellation of queued recovery shall prevent its provider callback without releasing ownership; recovery already dispatched shall complete and release only after successful reconciliation. Concurrent recovery requests shall not replay a completed successful provider recovery. Restart reconciliation shall require explicit confirmation, an exact current record and route mapping, and a separately qualified provider callback. Acceptance: Provider failure or failed durable acknowledgment retains quarantine; within the same process, retrying acknowledgment shall not replay successful provider cleanup. Control-owner heartbeat expiry shall permanently fence that lease without clearing its durable record. Explicit provider recovery may reconcile an expired retained session; generic release and late renewal shall not bypass reconciliation.

[REQUIREMENT]
UID: BD-LIFE-006
STATUS: Active
TITLE: Restart reconciliation P0
STATEMENT: The host shall durably record ownership and recovery state locally and reconcile interrupted sessions before accepting control after restart. Acceptance: Kill the host during dispatch and restart without a central database; affected resources remain unavailable pending reconciliation. Local records shall exclude reusable lease capabilities and retain canonical resource, route fingerprint, optional configuration revision and acquisition time. Acceptance: Reject corrupt, missing existing, duplicate, oversized and unsupported journal state at startup; enforce a single writer; restore interrupted ownership as quarantine, including orphaned registrations; reject old leases and stale reconciliation reviews. Missing or changed startup mappings shall block new physical grants so renaming cannot bypass quarantine. Clear evidence only after successful cleanup or explicit qualified reconciliation and durable acknowledgment. Process-termination evidence shall be distinguished from power-loss, platform and physical-device qualification.

[REQUIREMENT]
UID: BD-HB-001
STATUS: Active
TITLE: Bidirectional health P0
STATEMENT: Clients and authoritative instrument hosts shall exchange authenticated health messages including peer epoch and health sequence independently of instrument I/O. Acceptance: Block a device operation; peer health remains responsive while device readiness reports degradation. The local canonical host shall accept capability-authenticated heartbeat messages with exact host epoch, owner generation, fixed peer epoch and increasing sequence, returning a matching acknowledgment without acquiring the vendor-call gate. Acceptance: Renew while a measurement is blocked; a client rejects a mismatched acknowledgment and never interprets renewal as device readiness. Remote identity and TLS qualification remain separately required.

[REQUIREMENT]
UID: BD-HB-002
STATUS: Active
TITLE: Real-time deadlines P0
STATEMENT: Heartbeat and lease expiry shall use monotonic real time with validated finite interval, timeout and expiry settings independent of simulated time. Acceptance: Advance simulation or change wall clock; real lease expiration is unchanged; reject invalid budgets. Validate interval, suspect and expiry relationships at startup; absent host settings use finite defaults. Acceptance: Duplicate or out-of-order heartbeat messages do not extend last-seen time; wall-clock changes do not affect age or expiry, and exact expiry boundaries fence ownership. Acceptance: Reject scope renewal identifiers containing separators or control characters and periods above one minute before starting renewal. Acceptance: Concurrent and repeated scope heartbeat disposal shall share completion; start after disposal shall fail without issuing HTTP requests. Acceptance: A failed heartbeat observer shall not suppress subsequent observers or stop periodic renewal. Acceptance: Every scope heartbeat request shall have a real-time cancellation deadline clamped to one through ten seconds; timeout reports Degraded without releasing ownership. Acceptance: A successful transport response taking longer than a sub-second renewal period shall remain Healthy when it completes within the independent one-second minimum HTTP budget. Acceptance: Owner renewal HTTP budgets shall be clamped to one through ten seconds independently of sub-second host renewal intervals. Acceptance: Owner heartbeat setup shall reject nonfinite or negative ages, expired snapshots, invalid expiry-to-interval ratios and unsupported loss policies. Acceptance: Starting scope heartbeat shall dispatch the first renewal immediately, followed by the configured periodic schedule. Acceptance: Heartbeat configuration rejects unknown or nested settings and invalid provider frequency before serving owners. A backwards monotonic clock permanently fences the retained owner rather than restoring health. One validated timestamp supplies an observation and its detached age, and accepted renewal uses that observation. Clock sampling and generation-overflow validation precede grant mutation so failed grants do not leave partial reservations. Neither observations nor clock faults release ownership or dispatch device operations.









[REQUIREMENT]
UID: BD-HB-003
STATUS: Active
TITLE: Fenced ownership P0
STATEMENT: The authoritative host shall reject expired or stale owner commands using a restart-safe epoch and lease generation, including immediately before dispatch. Acceptance: Expire a queued command then renew with a new generation; old queued and replayed commands never reach the device. The canonical registry shall validate owner health before waiting and again immediately before command dispatch. Acceptance: A queued old-owner command cannot execute after expiry, a new generation or host restart; expiry cannot be reversed by renewal. Preserve in-flight ownership until completion and retain unresolved startup records. Acceptance: A failed fencing-ledger constructor shall release its writer lock while retaining corrupt state and the original failure for subsequent inspection. Acceptance: Scope heartbeat unauthorized and conflicting ownership responses shall report Lost and stop the renewal loop. Acceptance: Correct owner epochs and sequences shall not authorize acknowledgments with negative ages, changed timing budgets or unsupported loss policies. Acceptance: Scope transport OperationCanceledException without shutdown cancellation becomes Degraded and leaves the renewal loop available for recovery; scope health and validated owner acknowledgments are safely published across threads. Acceptance: Regression evidence must include recovery after a plain transport cancellation and concurrent owner renewals with unique serialized sequences and a coherent latest acknowledgment. Acceptance: Both client heartbeat helpers count observer failures without altering health outcomes and treat HTTP Gone as terminal loss. A disposed scope renewal helper reports Stopped without claiming that its host lease is released or hardware is safe. Acceptance: Focused heartbeat regressions cover terminal Gone replies, observer failure counts, idempotent stopped state and cancellation of an admitted renewal while retaining the caller-owned transport and issuing no lease-release request.








[REQUIREMENT]
UID: BD-HB-004
STATUS: Active
TITLE: Loss policy P0
STATEMENT: A missed heartbeat shall produce Suspect status; lease expiry shall fence old control and invoke the configured local safety policy before any reassignment. Acceptance: Inject one-way partition and delayed packets; no premature ownership transfer or false safe-state report. The initial local policy is FenceAndRetain: mark suspect on the first silence threshold, permanently fence at expiry and preserve ownership for explicit provider recovery. Acceptance: No callback, close, automatic replay or reassignment occurs merely because heartbeats stop; qualified orderly host shutdown remains a separate path.

[REQUIREMENT]
UID: BD-HB-005
STATUS: Active
TITLE: Multiple peer roles P0
STATEMENT: Each resource shall have one authoritative owner and an explicit policy distinguishing loss of control peers from loss of optional telemetry or database peers. Acceptance: Disconnect each peer independently; apply the configured pause, local continuation or shutdown policy without split-brain ownership. Read-only monitor/status requests and unrelated instrument heartbeats shall not renew the control owner. Acceptance: One silent experiment expires while another instrument continues receiving its own renewals; passive observers cannot prevent expiry or trigger device I/O.

[REQUIREMENT]
UID: BD-HB-006
STATUS: Active
TITLE: Readiness telemetry P0
STATEMENT: Health snapshots shall distinguish process responsiveness, instrument readiness, last device success and data staleness without observer-triggered device queries. Acceptance: Keep heartbeat alive while device fails; dashboard marks device unhealthy and cached samples stale. Local cached DMM status shall carry owner health separately from device state, last successful device operation, last successful reading receipt time and monotonic reading age. Acceptance: Device failure with healthy heartbeat retains the prior success/reading metadata; clock changes do not reset reading age. Persisted per-role freshness policies and independent observer thresholds have local implementation; integrated fleet dashboards remain separate acceptance work. Acceptance: Cached DMM status distinguishes owner responsiveness, device state, last device success and last successful reading. Monotonic age survives UTC changes and faults. Each status request may supply an independent finite freshness budget of 1 through 86400000 milliseconds; missing samples are Missing, samples without a budget are Unspecified, and age at or above the limit is Stale. Inspection never queries the device or renews ownership. The local setup page displays all health dimensions and a tab-specific budget with snapshot-at-refresh wording. Fleet dashboards and automatic experiment policy persistence remain unfinished. Acceptance: Setup roles may persist an optional finite reading freshness budget of 1 through 86400000 milliseconds. Strict import, saved-file read and save reject invalid policy without replacing prior evidence. Activation pins the selected role policy and revision before provider I/O; later saves do not alter active status. Omitted status overrides use the pinned policy and explicit overrides remain per observer. The setup page edits saved limits, distinguishes pinned/applied limits, and offers an explicit transient override. Legacy role construction and two-field deconstruction remain available. Fleet dashboards and real-browser acceptance remain unfinished.



[REQUIREMENT]
UID: BD-CMD-001
STATUS: Active
TITLE: Command envelope P0
STATEMENT: Every remote control command shall carry protocol version, unique command ID, run ID, canonical resource ID, owner generation, payload hash and deadline. Acceptance: Reject missing, incompatible or unauthorized envelopes before instrument I/O.

[REQUIREMENT]
UID: BD-CMD-002
STATUS: Active
TITLE: Durable acceptance P0
STATEMENT: The host shall acknowledge Accepted only after validation and local durable command recording, and report Started and terminal Completed, Failed, Rejected, Cancelled or OutcomeUnknown states. Acceptance: Crash after acceptance; command status is recoverable; disk-full prevents acceptance and dispatch.

[REQUIREMENT]
UID: BD-CMD-003
STATUS: Active
TITLE: Duplicate reconciliation P0
STATEMENT: Duplicate command IDs with matching owner scope and payload shall return recorded state; conflicting reuse shall be rejected without repeating physical effects. Acceptance: Submit simultaneous duplicates and a changed-payload duplicate; dispatch at most once within the recorded execution attempt.

[REQUIREMENT]
UID: BD-CMD-004
STATUS: Active
TITLE: Status lookup P0
STATEMENT: After a lost response clients shall query authorized command status by ID; indeterminate dispatch after a crash shall be OutcomeUnknown until reconciled. Acceptance: Drop completion reply and crash between physical effect and journal update; do not silently retry or report success.

[REQUIREMENT]
UID: BD-CMD-005
STATUS: Active
TITLE: Completion evidence P0
STATEMENT: Completed receipts shall identify whether completion evidence is transport write, instrument-reported completion or verified physical state. Acceptance: Use a device accepting writes but not reaching target; never label transport completion as physical verification.

[REQUIREMENT]
UID: BD-CMD-006
STATUS: Active
TITLE: Retry policy P0
STATEMENT: Automatic retries shall be bounded by deadline and attempt budget and require an explicit operation-specific safe-repeat classification; uncertain non-idempotent actuation shall not be replayed automatically. Acceptance: Test pulse/trigger/buffer reads, absolute setters and transient reconnects; unsafe operations never repeat and safe retry budgets terminate.

[REQUIREMENT]
UID: BD-CMD-007
STATUS: Active
TITLE: Typed errors P0
STATEMENT: Local exceptions and remote faults shall preserve stable error code, stage, resource, command correlation, retry disposition and outcome certainty while redacting sensitive internals. Acceptance: Inject validation, lease, transport, timeout, protocol and cleanup faults; client receives distinct typed outcomes and correlated local diagnostics.

[REQUIREMENT]
UID: BD-CMD-008
STATUS: Active
TITLE: Backpressure and cancellation P0
STATEMENT: Command queues shall have bounded capacity and explicit overload rejection; cancellation before dispatch shall prevent I/O, while cancellation after dispatch shall preserve outcome uncertainty and recovery policy. Acceptance: Saturate queue, cancel queued and running commands, then expire lease; assert bounds and accurate outcomes.

[REQUIREMENT]
UID: BD-RES-001
STATUS: Active
TITLE: Fault injection P0
STATEMENT: Automated acceptance shall exercise message loss, duplication, reordering, partitions, disk-full, process restart and non-cooperative drivers across lifecycle and command states. Acceptance: Record a matrix of passing assertions for no stale actuation, no unsafe replay and bounded recovery decisions.

[REQUIREMENT]
UID: BD-RES-002
STATUS: Active
TITLE: External protection boundary P0
STATEMENT: Instrument policies shall identify hazards needing independent hardware watchdogs or interlocks and shall not claim software shutdown executes after process or power loss. Acceptance: Kill the host and document the tested hardware protection or explicitly record that protection is unavailable.

[REQUIREMENT]
UID: BD-RES-003
STATUS: Active
TITLE: Evidence retention P0
STATEMENT: Resilience verification shall retain tested commit, platform, configuration, fault schedule, assertions and logs, distinguishing simulations from hardware results. Acceptance: Reproduce a fault case from recorded configuration and reject verification claims lacking execution evidence.

[REQUIREMENT]
UID: BD-ID-001
STATUS: Active
TITLE: Identification on open P0
STATEMENT: Every supported framework open and reconnect shall obtain declared instrument identification before enabling control and record unsupported or failed identification explicitly. Acceptance: Test supported, unsupported, empty and failed identification on direct, generated, async and remote paths.

[REQUIREMENT]
UID: BD-ID-002
STATUS: Active
TITLE: Durable identity history P0
STATEMENT: Identity observations shall be locally durably logged with resource, backend, UTC time and available manufacturer, model, serial and firmware, without requiring a central database. Acceptance: Restart offline and recover identification history including nonstandard responses and failed attempts.

[REQUIREMENT]
UID: BD-ID-003
STATUS: Active
TITLE: Identity dashboard P0
STATEMENT: Dashboards shall show cached observed identity, observation age, lock policy, authenticated owner/run and connection state without revealing lease secrets or issuing extra device queries. Acceptance: Poll before/during/after reservation and disconnect; identity remains attributable, stale state is explicit and bearer tokens are absent.

[REQUIREMENT]
UID: BD-ID-004
STATUS: Active
TITLE: Substitution detection P0
STATEMENT: Reconnect shall invalidate stale identity and compare configured manufacturer, model or serial constraints before allowing control. Acceptance: Replace the device at the same address; reject control on mismatch until authorized reconciliation.

[REQUIREMENT]
UID: BD-OWN-001
STATUS: Active
TITLE: Reviewed sharing metadata P0
STATEMENT: Instrument definitions shall declare exclusive-by-default access, whole-instrument lock scope, coupled resources, native lock support, identity provider, operation side effects and lifecycle policy with review provenance. Acceptance: Reject unreviewed independent-channel or shared-query claims; preserve these fields through import and generation.

[REQUIREMENT]
UID: BD-OWN-002
STATUS: Active
TITLE: Transaction and run ownership P0
STATEMENT: The host shall serialize complete transport transactions and protect configure/acquire sequences with experiment ownership independently of optional native device locks. Acceptance: Interleave two clients and coupled channels; no response crossover or configuration interference; cached observers issue no I/O.

[REQUIREMENT]
UID: BD-REQ-006
STATUS: Active
TITLE: Change traceability P0
STATEMENT: Every accepted feature or behavior change shall update stable requirements, acceptance criteria, traceability, issue links and verification evidence in the same change; deferred features shall remain explicitly tracked. Acceptance: Review a feature change and its linked requirement diff; the static gate rejects missing rows, acceptance criteria or issue links.

[REQUIREMENT]
UID: BD-CFG-001
STATUS: Active
TITLE: BD-CFG-001 P0
STATEMENT: The instrument client shall resolve roles through an optional versioned instrument-location file mapping host origins and canonical host-local resource IDs. Acceptance: Load a local and remote mapping and verify the exact target resource and URI with a fake HTTP transport.

[REQUIREMENT]
UID: BD-CFG-002
STATUS: Active
TITLE: BD-CFG-002 P0
STATEMENT: When the conventional configuration file is absent the framework shall resolve instrument IDs to the localhost server and log the default decision and selected route. Acceptance: Resolve DMM1 without instruments.json and assert localhost endpoint and both log records. Acceptance: Routing decisions and configuration rejection shall retain their documented outcomes when logging sinks throw.


[REQUIREMENT]
UID: BD-CFG-003
STATUS: Active
TITLE: BD-CFG-003 P0
STATEMENT: Explicit missing, malformed, ambiguous, unsupported or incomplete routing configuration shall fail without silently choosing a local or different instrument. Acceptance: Reject invalid versions, duplicate keys, unknown fields/hosts/roles and unsafe endpoints; verify no fallback request. Acceptance: Null roles and identifiers ending with newlines shall fail validation without creating a route. Acceptance: Out-of-range numeric routing schema versions shall raise InvalidDataException without local fallback.



[REQUIREMENT]
UID: BD-CFG-004
STATUS: Active
TITLE: BD-CFG-004 P0
STATEMENT: Configured routing shall support multiple experiment clients and cached read-only observers per server while preserving exclusive ownership of each canonical resource. Acceptance: Reserve two distinct resources concurrently, reject a competing reservation for one resource and allow multiple observer snapshots. Confirmed Ethernet and GPIB aliases of one instrument shall use the same authoritative owner and reservation; two experiments using different aliases shall contend for that same resource, while distinct instruments on separate buses remain independently reservable.

[REQUIREMENT]
UID: BD-CFG-005
STATUS: Active
TITLE: BD-CFG-005 P0
STATEMENT: Routing configuration shall exclude credentials, use HTTPS for non-loopback endpoints and remain immutable for each loaded snapshot; route logging shall not expose secrets. Acceptance: Reject credential-bearing URLs, retain caller HTTP settings, and verify that invalid configuration logs omit secret values.

[REQUIREMENT]
UID: BD-CFG-006
STATUS: Active
TITLE: BD-CFG-006 P1
STATEMENT: Dependency setup shall discover all project references, install a compatible SDK and pinned documentation tools, and offer browser provisioning without a separate PowerShell requirement on Unix. Acceptance: Run setup on clean supported operating systems and restore every project including the browser installer; report missing system prerequisites explicitly. Acceptance: A .NET 10 SDK in a later feature band shall run local project tests without editing global.json.


[REQUIREMENT]
UID: BD-CFG-007
STATUS: Active
TITLE: BD-CFG-007 P1
STATEMENT: A generated searchable requirements scoreboard and documented local/remote examples shall reflect canonical statuses and distinguish source, execution evidence and planned capabilities. Acceptance: Generate scoreboard from traceability and verify total/status counts, filtering markup, escaped values and links; review setup and routing examples. Acceptance: The C# scoreboard shall emit byte-identical escaped HTML, including empty and quoted Unicode inventories; default execution shall use the measured fastest equivalent implementation. Acceptance: The full check workflow shall generate the same escaped scoreboard without requiring native compilation on a cold run; performance reports shall distinguish empty build caches from OS and package caches. Acceptance: Compiled check builds partition caches by OS runtime identifier and Debug/Release configuration, fingerprint the SDK and source contents, validate artifact hashes, reject unsupported architecture combinations and require matching process architecture before executing checks. Native Make publishing requires an explicit runtime identifier. Acceptance: Focused regressions cover all eight supported runtime build plans, automatic host selection, cross-architecture execution prohibition, unsupported inputs, SDK identity, corrupt artifacts and Debug/Release cache isolation. Non-local runtime plans are contract-tested without claiming foreign runtime execution. Acceptance: GPIB and USB discovery reject an Ethernet host argument rather than silently ignoring a mismatched scope selection. Acceptance: Setup JSON import and save envelopes reject more than one Mi characters or nesting beyond 32 levels. Saved setup reads enforce a bounded UTF-8 file size and propagate unreadable files rather than silently treating them as absent; oversized serialized saves are rejected before replacing the prior revision. Acceptance: Focused configuration regressions exercise all four import boundaries, nesting rejection, repair after oversized saved-file rejection, and preservation of the previous revision and exact file bytes after an oversized structurally valid draft save. Acceptance: Compiled tooling respects explicit .NET executable selection and partitions normal and optional standalone Roslyn outputs by runtime identifier and configuration. Optional native parity explicitly receives the selected native and Roslyn paths; default checks avoid native compilation. Unsupported or mismatched execution architectures remain rejected before checks. Acceptance: Compiled check entry points accept canonical explicit runtime identifiers, infer architecture only when automatic, and reject RID/architecture conflicts or unsupported cross-OS requests before cache mutation. Normal Make check targets forward RID when supplied. Optional native and standalone Roslyn targets always validate runtime plans even on cached hits. Port verification rejects cross-architecture execution before recursive builds and checks actual .NET host identity; managed parity DLLs are partitioned by runtime and configuration. Acceptance: The primary Make-free developer entry point shall use the shared compiled C# host for checks, generation, application builds and non-browser tests, preserve selected executable and configuration arguments, stop on the first failed prerequisite, and expose an ordered JSON task plan without launching task subprocesses. Make remains an optional compatibility wrapper; architecture validation and cache isolation remain shared with the existing bootstrap. Acceptance: Application task planning skips absent optional trees and excludes build artifacts and symbolic links without traversing them. Child tasks receive bounded timeouts and preserve selected executable/configuration/filter argument boundaries; failed launch, timeout or cancellation stops subsequent work and produces a structured stage report. Plan mode starts no task subprocesses and leaves execution reports untouched. Build orchestration owns no instrument lease or physical device command.










[REQUIREMENT]
UID: BD-DOC-003
STATUS: Active
TITLE: BD-DOC-003 P1
STATEMENT: The project shall generate a browsable CSharp XML-comment API reference and Python docstring reference using pinned tools provisioned by setup. Acceptance: Build the combined site on a clean supported host, navigate API and Python pages and publish the build artifact; report unresolved links and tool failures.

[REQUIREMENT]
UID: BD-DOC-004
STATUS: Active
TITLE: BD-DOC-004 P1
STATEMENT: All owned public CSharp APIs and Python modules/functions shall have accurate purpose, parameter, units, return, error, ownership and cancellation documentation as applicable. Acceptance: Audit every source area, resolve the tracked legacy gaps through semantic review and reject new undocumented APIs; signatures alone do not count as completed descriptions. Acceptance: C# documentation tooling shall preserve reference report bytes, exit codes and diagnostic order at one and eight workers; Python source shall only be parsed, never executed; scanner selection shall be benchmarked. Acceptance: The combined C# workflow shall regenerate byte-identical reports using shared authoritative Roslyn and port code; independent checks may overlap while documentation and comparison await their producer reports. Acceptance: All Make requirements/documentation check and report entry points use the shared compiled C# host; Python remains the parser and independent parity reference. Unknown or duplicate workflow options and invalid worker/time limits fail before check execution. Focused tests for the 150-iteration batch execute at iterations 50, 100 and 150. Acceptance: At focused checkpoints, the complete compiled checks-only workflow must reproduce all six independent reference report byte hashes at worker counts one and eight, with seven successful stages and no application tests. Acceptance: Standalone documentation and comparison commands regenerate their Roslyn and portable producer reports before consumption and stop on producer failure. Make forwards the selected .NET executable to the compiled bootstrap; cache reuse fingerprints its resolved path and SDK. Build-cache contenders wait for a bounded lock instead of immediately failing. CI release neutrality uses the same managed compiled host; Python remains an independent reference. Acceptance: Optional parity and benchmark tools honor explicit .NET host, managed DLL, native executable and Roslyn assembly selections. Missing explicitly selected tools fail rather than silently reducing verification scope. Normal requirements/documentation/report execution remains the shared compiled C# host; reference Python remains only the parser and independent test harness.







[REQUIREMENT]
UID: BD-DOC-005
STATUS: Active
TITLE: BD-DOC-005 P1
STATEMENT: Every instrument or code generator shall emit API documentation through the same pipeline as handwritten code. Acceptance: Regenerate driver and mock fixtures, verify units, limits, channel, cancellation and ownership comments, reject undocumented generated members even if present in a legacy baseline, and render the generated APIs.

[REQUIREMENT]
UID: BD-ART-001
STATUS: Active
TITLE: BD-ART-001 P1
STATEMENT: A backend-neutral artifact service shall save binary captures by stable artifact ID with searchable run, acquisition and instrument metadata, while supporting local-only operation and optional central storage. Acceptance: Save and retrieve a trace and screenshot by acquisition after restart and storage relocation without application-owned filenames.

[REQUIREMENT]
UID: BD-ART-002
STATUS: Active
TITLE: BD-ART-002 P0
STATEMENT: Artifact durability acknowledgments shall follow verified immutable bytes and committed ready metadata; pending states and replication outbox shall support restart reconciliation. Acceptance: Inject failure at every write/commit boundary and recover staging, orphaned objects and interrupted uploads without exposing incomplete captures or falsely acknowledging durability.

[REQUIREMENT]
UID: BD-ART-003
STATUS: Active
TITLE: BD-ART-003 P1
STATEMENT: Waveform artifacts shall preserve original bytes and a versioned decoding manifest with acquisition identity, units, encoding, timebase and available calibration/settings; screenshots and derived previews shall link to the acquisition and source artifact. Acceptance: Decode a saved trace with correct axes after restart, explicitly retain unknown metadata as absent and retrieve its linked screenshot.

[REQUIREMENT]
UID: BD-ART-004
STATUS: Active
TITLE: BD-ART-004 P0
STATEMENT: Artifact storage shall stream with bounded memory, verify byte counts and digests, enforce quotas and ownership-aware retention, and surface recording faults. Acceptance: Save a capture larger than process memory, detect corruption/disk exhaustion, preserve referenced data during retention and restore an exported manifest plus all bytes on an empty host.

[REQUIREMENT]
UID: BD-ART-005
STATUS: Active
TITLE: BD-ART-005 P2
STATEMENT: Binary storage adapter and size-threshold choices shall be supported by representative workload measurements rather than assuming all database blobs are slow. Acceptance: Compare embedded BLOB, managed local files and the selected central object backend using capture sizes, concurrency, durability, range reads and restore costs, publishing configuration and latency/throughput evidence.

[REQUIREMENT]
UID: BD-DEF-009
STATUS: Active
TITLE: BD-DEF-009 P0
STATEMENT: A review gate shall prevent unreviewed or incomplete instrument definitions from being eligible for generation and require provenance, reviewer and manual evidence.

[REQUIREMENT]
UID: BD-DEF-010
STATUS: Active
TITLE: BD-DEF-010 P1
STATEMENT: Static extraction shall report potentially missing inherited and dynamic instrument members without claiming full method coverage.

[REQUIREMENT]
UID: BD-DEF-011
STATUS: Active
TITLE: BD-DEF-011 P1
STATEMENT: The Instrument Definer shall batch-extract a pinned manifest of external instrument source instruments with per-instrument diagnostics and no overwrites.

[REQUIREMENT]
UID: BD-CFG-008
STATUS: Active
TITLE: BD-CFG-008 P1 Discovery-assisted inventory
STATEMENT: The setup workflow shall discover supported controllers and instrument endpoints within an operator-selected host and network scope, showing transport, controller, address, available identity metadata, busy status and actionable diagnostics without requiring manual VISA syntax for discovered devices. Device probes shall respect the canonical ownership authority and shall not alter device configuration. Acceptance: Display an Ethernet instrument and two USB-GPIB controllers, distinguish missing provider from no response, allow cancellation, and show an actively reserved instrument from cached metadata without issuing probe I/O. Acceptance: Ethernet discovery shall reject empty, overlong and hyphen-ended DNS labels before invoking the catalog. Acceptance: Discovery shall accept USB and Ethernet endpoints only with complete transport-specific INSTR descriptor shapes within the selected scope. Acceptance: Injected and native VISA inventories shall reject more than 4096 entries, overlong descriptors or control characters and propagate cancellation during translation. Acceptance: GPIB primary addresses shall use decimal tokens without signs or whitespace and optional USB interface components shall be unsigned integers.





[REQUIREMENT]
UID: BD-CFG-009
STATUS: Active
TITLE: BD-CFG-009 P1 Optional identity metadata
STATEMENT: Instrument and controller serial numbers shall be optional for setup, generated configuration and use; discovery shall populate available metadata without requiring transcription. The workflow shall distinguish discovered metadata, operator-confirmed associations and optional enforced identity checks. Acceptance: Save and reload a usable no-serial configuration; keep two same-model instruments with absent or duplicate serials separate; enable an explicit expected-identity check and reject a mismatch without substituting another device.

[REQUIREMENT]
UID: BD-CFG-010
STATUS: Active
TITLE: BD-CFG-010 P1 Human-assisted controller binding
STATEMENT: The setup workflow shall let operators identify and name multiple controllers and bind each to its host/provider and available stable identifier or an explicitly confirmed mapping when no stable identifier exists. GPIB instrument addresses shall be scoped to the controller bus, and ambiguous or changed bindings shall require review rather than choosing the first adapter. Acceptance: Configure address 22 on each of two independent USB-GPIB buses without a collision; reconnect or reorder adapters and either retain a verified stable binding or show a repair prompt; complete setup without entering adapter serial numbers.

[REQUIREMENT]
UID: BD-CFG-011
STATUS: Active
TITLE: BD-CFG-011 P1 Operator-confirmed alternate connections
STATEMENT: The setup workflow shall represent one physical instrument with a canonical identity and one or more named connection routes, allow an operator to confirm alternate routes belong to that instrument, select a route and assign logical experiment roles. Discovery suggestions shall not silently merge devices based on model, address or unverified serial metadata. Acceptance: Associate Ethernet and GPIB routes with one instrument, retain two identical no-serial devices as separate instruments, and review or undo a proposed association before saving; reserve confirmed aliases under the existing BD-CFG-004 ownership contract.

[REQUIREMENT]
UID: BD-CFG-012
STATUS: Active
TITLE: BD-CFG-012 P1 Guided setup and configuration repair
STATEMENT: The setup workflow shall guide discovery, identification and naming, alternate-route association, role assignment, validation and review/save, while supporting manual entry and offline editing of versioned configuration. It shall explain unresolved or ambiguous mappings, distinguish untested configuration from validated connections, preserve the prior saved configuration after failed validation or cancelled editing, and provide repair when bench connections change. Acceptance: Complete a simple Ethernet setup without a serial or typed VISA string; save an explicitly untested offline draft; export and reload equivalent role/controller/route mappings; repair a missing adapter with an old/new preview and no mutation of active run snapshots. Device validation shall use the canonical reservation authority and shall not reset or enable outputs. Reviewed IVI binding import shall preserve the source revision, declared module, driver session, original resource descriptor and standard option/channel maps in a versioned offline draft. Acceptance: Require explicit target/association confirmation; reject stale catalogs, duplicate physical route assignment and conflicting role replacement; roundtrip bindings without requiring serial numbers; keep schema-one configurations readable; block activation and device probes for unsupported bindings. The setup tab shall retain its IVI lease capability in session storage across reload, inspect cached host state before permitting operations, retain the capability after transient inspection failure, and discard a host-rejected stale capability without claiming physical recovery. It shall suppress overlapping instrument button actions and consume each activation/recovery confirmation at dispatch; reload shall never reopen or automatically retry a driver. Operators shall be able to inspect a privately retained lease capability from another tab without opening a driver, replacing an active tab lease, or bypassing host validation. Measurement controls shall list declared provider functions and render response units and provenance without deriving units from a later status snapshot. Setup shall inspect unresolved startup ownership and show missing providers or changed route mappings. Acceptance: Require a fresh successful inspection and explicit confirmation for each reconciliation attempt; consume confirmation on failure, invalidate stale reviews after failed inspection, and never reopen a driver or infer physical recovery from a stale browser lease. The setup tab shall renew its retained control owner independently of instrument actions, validate acknowledgment epoch/generation/peer/sequence and stop on terminal ownership rejection. Acceptance: Never reopen after loss, retain recovery details, stop renewal after close or page departure, reject stale lifecycle inspection responses and show shutdown outcomes without providing a browser stop-host action.
